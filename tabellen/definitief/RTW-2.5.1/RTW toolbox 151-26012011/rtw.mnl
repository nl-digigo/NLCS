;; **************************************************************************************
;; File         : RTW.mnl
;; Hoofdfunctie : n.v.t. 
;; Doel         : laden RTW (functies)
;; Beperkingen  : geen   
;; Opmerkingen  : geen   
;; **************************************************************************************
;;
;; Naam               | Dienst en Omschrijving                      | Datum      | Versie
;; -------------------+---------------------------------------------+------------+-------
;; Jan Peter de Smidt | Bouwdienst                                  | 01-03-2000 | 1.00  
;;                    |    Bouw                                     |            |       
;;                    |    Wijzigingen tov versie 1.0 :             |            |       
;; A.F. Sandbergen    | NedGraphics i.o.v. Bouwdienst               | 22-05-2000 | 1.01  
;;                    |    Redesign en systeemdocumentatie          |            |       
;;                    |    Belangrijke wijzigingen:                 |            |       
;;                    |    - controle hoofdpad te bepalen           |            |       
;;                    |    - geen globale variabelen en dus alles   |            |       
;;                    |      d.m.v. parameters doorgeven            |            |       
;; A.F. Sandbergen    | NedGraphics i.o.v. Bouwdienst               | 07-09-2001 | TB-03 
;;                    |    Aanbrengen aanpassingen t.b.v. 2000[i]   |            |       
;;                    |    W. Pronk; document: 3322O-C2-01009       |            |       
;; T. van der Meiden  | NedGraphics i.o.v. Bouwdienst               | 18-10-2004 | 1.3 
;;                    |    Aanbrengen aanpassingen uitbreiding      |            |       
;;                    |    W. Pronk; document: 7417-T0409-001.doc   |            |       
;; W. Pronk           | Bouwdienst                                  | 01-05-2007 | 1.4 
;;                    |    Aanbrengen aanpassingen                  |            |     
;; W. Pronk           | DID                                         | 10-05-2010 | 1.5 
;;                    |    Aanbrengen aanpassingen                  |            |            
;; W. Pronk           | DID                                         | 27-01-2010 | 1.51 
;;                    |    Aanbrengen aanpassingen                  |            |      
;; **************************************************************************************

;; Melden welk programma wordt geladen.
(princ "\nRTW tools - versie TB 1.51 versie 2004/2010-(laden)\n")

;; De hoofd-directory van RTW-invullen. Deze globale variabele wordt
;; veelvuldig gebruikt t.b.v. opzoeken DCL-files en dergelijke.
;; Nb. deze instelling moet in configuratie-file worden geplaatst.

(setq #rtw_hfddir (findfile "RTW.mnl"))
(setq len (- (strlen #rtw_hfddir) ( strlen "RTW.mnl") 1))
(setq #rtw_hfddir (substr #rtw_hfddir 1 len))	 

;; Controle of de gevraagde hoofd-directory bestaat. Indien
;; nog niet ingevuld, deze a.d.h.v. AutoCAD config. file bepalen.

(if (or (= #rtw_hfddir nil) (= #rtw_hfddir ""))
   (progn

      (setq #rtw_hfddir (getcfg "AppData/RTW/RTW_directory"))
      (if (or (= #rtw_hfddir nil) (= #rtw_hfddir ""))
         (setq #rtw_hfddir (getcfg "AppData/RTW/RTW_directory"))
      )

      ;; Als er nu nog geen hoofd-directory bestaat,
      ;; dan houdt alles op. Geen oplossing mogelijk.
      (if (or (= #rtw_hfddir nil) (= #rtw_hfddir ""))
         (progn
            (setq correct "Kan setting <RTW_directory> niet vinden.\n"
	          correct (strcat correct "Voeg de setting toe aan de AutoCAD config.file\n")
	          correct (strcat correct "of voeg het pad toe naar RTW-hoofddirectory.")
            )

            (princ "\n\n")
            (princ correct)
            (princ "\n\n")

            (alert correct)
            (setq correct nil)
            (exit)
         )
      )
   )
)

;; Hoofd-directory gelijk opslaan in config.file.
;; Nb. geheel RTW maakt daar straks gebruik van.
(setcfg "AppData/RTW/RTW_directory" #rtw_hfddir)

;; Laden van de file met RTW (totaal LSP + DCL).
(if (= (member "rtw.vlx" '(vlx)) nil)
   (progn
      (setq file (strcat #rtw_hfddir "\\support\\RTW.vlx"))
      (if (findfile file)
         (load file)
;;    else
         (progn
            (princ "\nFile <")(princ file)(princ "> niet gevonden.\n")
         )
      )
   )
)


;; Laden van de file met RTW_reactor en aanzetten.
(setq file (strcat #rtw_hfddir "\\support\\RTW_reactor_load.lsp"))
(if (findfile file)
   (progn
      (load file)
      (c:RTW_load_reactor_on)
   )
;; else
   (progn
      (princ "\nFile <")(princ file)(princ "> niet gevonden.\n")
   );;endprogn
);;endif


(princ "\n")
(princ "\nRTW tools - versie TB 1.51 versie 2004/2010(geladen)\n")
(princ)
